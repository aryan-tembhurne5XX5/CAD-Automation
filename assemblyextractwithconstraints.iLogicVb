Sub Main()

    Dim asmDoc As AssemblyDocument = ThisApplication.ActiveDocument
    If asmDoc.DocumentType <> DocumentTypeEnum.kAssemblyDocumentObject Then
        MessageBox.Show("This rule must run inside an Assembly (.iam)")
        Exit Sub
    End If

    Dim asmDef As AssemblyComponentDefinition = asmDoc.ComponentDefinition
    Dim sb As New System.Text.StringBuilder()
    Dim Q As String = Chr(34)

    sb.AppendLine("{")

    '=================================================
    ' ASSEMBLY METADATA
    '=================================================
    sb.AppendLine("  " & Q & "assembly_metadata" & Q & ": {")
    sb.AppendLine("    " & Q & "assembly_name" & Q & ": " & Q & EscapeJson(asmDoc.DisplayName) & Q & ",")
    sb.AppendLine("    " & Q & "full_file_path" & Q & ": " & Q & EscapeJson(asmDoc.FullFileName.Replace("\", "/")) & Q & ",")
    sb.AppendLine("    " & Q & "internal_name" & Q & ": " & Q & EscapeJson(asmDoc.InternalName) & Q & ",")
    sb.AppendLine("    " & Q & "units" & Q & ": " & Q & "mm" & Q & ",")

    sb.AppendLine("    " & Q & "mass_kg" & Q & ": " & FormatNumber(asmDef.MassProperties.Mass) & ",")
    sb.AppendLine("    " & Q & "volume_cm3" & Q & ": " & FormatNumber(asmDef.MassProperties.Volume / 1000) & ",")

    Dim cog As Point = asmDef.MassProperties.CenterOfMass
    sb.AppendLine("    " & Q & "center_of_gravity_mm" & Q & ": {")
    sb.AppendLine("      " & Q & "x" & Q & ": " & FormatNumber(cog.X * 10) & ",")
    sb.AppendLine("      " & Q & "y" & Q & ": " & FormatNumber(cog.Y * 10) & ",")
    sb.AppendLine("      " & Q & "z" & Q & ": " & FormatNumber(cog.Z * 10))
    sb.AppendLine("    },")

    sb.AppendLine("    " & Q & "author" & Q & ": " & Q & EscapeJson(GetProp(asmDoc, "Summary Information", "Author")) & Q & ",")
    sb.AppendLine("    " & Q & "total_occurrences" & Q & ": " & asmDef.Occurrences.AllLeafOccurrences.Count & ",")
    sb.AppendLine("    " & Q & "total_constraints" & Q & ": " & asmDef.Constraints.Count & ",")
    sb.AppendLine("    " & Q & "extraction_timestamp" & Q & ": " & Q & DateTime.Now.ToString("yyyy-MM-ddTHH:mm:ss") & Q)
    sb.AppendLine("  },")

    '=================================================
    ' COMPONENTS
    '=================================================
    sb.AppendLine("  " & Q & "components" & Q & ": [")

    Dim occs = asmDef.Occurrences.AllLeafOccurrences
    Dim occList As New List(Of ComponentOccurrence)
    Dim idx As Integer = 0

    For Each occ As ComponentOccurrence In occs
        occList.Add(occ)

        Dim partNum As String = occ.Name
        Dim partMass As Double = 0

        Try
            partNum = occ.Definition.Document.PropertySets _
                .Item("Design Tracking Properties").Item("Part Number").Value.ToString()
        Catch
        End Try

        Try
            partMass = occ.MassProperties.Mass
        Catch
        End Try

        Dim bbox As Box = occ.RangeBox

        sb.AppendLine("    {")
        sb.AppendLine("      " & Q & "occurrence_name" & Q & ": " & Q & EscapeJson(occ.Name) & Q & ",")
        sb.AppendLine("      " & Q & "file_name" & Q & ": " & Q & EscapeJson(occ.Definition.Document.DisplayName) & Q & ",")
        sb.AppendLine("      " & Q & "full_file_path" & Q & ": " & Q & EscapeJson(occ.Definition.Document.FullFileName.Replace("\", "/")) & Q & ",")
        sb.AppendLine("      " & Q & "internal_name" & Q & ": " & Q & EscapeJson(occ.Definition.Document.InternalName) & Q & ",")
        sb.AppendLine("      " & Q & "part_number" & Q & ": " & Q & EscapeJson(partNum) & Q & ",")
        sb.AppendLine("      " & Q & "mass_kg" & Q & ": " & FormatNumber(partMass) & ",")

        sb.AppendLine("      " & Q & "bounding_box_mm" & Q & ": {")
        sb.AppendLine("        " & Q & "min" & Q & ": { " & Q & "x" & Q & ": " & FormatNumber(bbox.MinPoint.X * 10) & ", " & Q & "y" & Q & ": " & FormatNumber(bbox.MinPoint.Y * 10) & ", " & Q & "z" & Q & ": " & FormatNumber(bbox.MinPoint.Z * 10) & " },")
        sb.AppendLine("        " & Q & "max" & Q & ": { " & Q & "x" & Q & ": " & FormatNumber(bbox.MaxPoint.X * 10) & ", " & Q & "y" & Q & ": " & FormatNumber(bbox.MaxPoint.Y * 10) & ", " & Q & "z" & Q & ": " & FormatNumber(bbox.MaxPoint.Z * 10) & " }")
        sb.AppendLine("      },")

        sb.AppendLine("      " & Q & "instance_index" & Q & ": " & idx)
        sb.Append("    }")

        idx += 1
        If idx < occs.Count Then sb.AppendLine(",") Else sb.AppendLine()
    Next

    sb.AppendLine("  ],")

    '=================================================
    ' CONSTRAINTS (NULL-SAFE)
    '=================================================
    sb.AppendLine("  " & Q & "constraints" & Q & ": [")

    Dim constraintList As New List(Of AssemblyConstraint)
    For Each c As AssemblyConstraint In asmDef.Constraints
        If Not c.Suppressed Then constraintList.Add(c)
    Next

    Dim cIdx As Integer = 0

    For Each c As AssemblyConstraint In constraintList

        Dim occ1 As ComponentOccurrence = Nothing
        Dim occ2 As ComponentOccurrence = Nothing
        Try : occ1 = c.OccurrenceOne : Catch : End Try
        Try : occ2 = c.OccurrenceTwo : Catch : End Try

        Dim occ1Idx As Integer = If(occ1 Is Nothing, -1, GetOccurrenceIndex(occList, occ1.Name))
        Dim occ2Idx As Integer = If(occ2 Is Nothing, -1, GetOccurrenceIndex(occList, occ2.Name))

        Dim distance As String = "null"
        If occ1 IsNot Nothing AndAlso occ2 IsNot Nothing Then
            Dim b1 As Box = occ1.RangeBox
            Dim b2 As Box = occ2.RangeBox
            Dim dx = ((b2.MinPoint.X + b2.MaxPoint.X) - (b1.MinPoint.X + b1.MaxPoint.X)) / 2
            Dim dy = ((b2.MinPoint.Y + b2.MaxPoint.Y) - (b1.MinPoint.Y + b1.MaxPoint.Y)) / 2
            Dim dz = ((b2.MinPoint.Z + b2.MaxPoint.Z) - (b1.MinPoint.Z + b1.MaxPoint.Z)) / 2
            distance = FormatNumber(Math.Sqrt(dx * dx + dy * dy + dz * dz) * 10)
        End If

        sb.AppendLine("    {")
        sb.AppendLine("      " & Q & "constraint_id" & Q & ": " & Q & EscapeJson(c.Name) & Q & ",")
        sb.AppendLine("      " & Q & "constraint_type" & Q & ": " & Q & c.Type.ToString() & Q & ",")

        sb.AppendLine("      " & Q & "component_pair" & Q & ": {")
        sb.AppendLine("        " & Q & "occurrence_one_index" & Q & ": " & occ1Idx & ",")
        sb.AppendLine("        " & Q & "occurrence_two_index" & Q & ": " & occ2Idx & ",")
        sb.AppendLine("        " & Q & "distance_between_centers_mm" & Q & ": " & distance)
        sb.AppendLine("      }")

        sb.Append("    }")

        cIdx += 1
        If cIdx < constraintList.Count Then sb.AppendLine(",") Else sb.AppendLine()
    Next

    sb.AppendLine("  ]")
    sb.AppendLine("}")

    Dim outPath As String = System.IO.Path.ChangeExtension(asmDoc.FullFileName, "_ml_ready.json")
    System.IO.File.WriteAllText(outPath, sb.ToString())

    MessageBox.Show("✅ ML-READY Assembly Extraction Complete!" & vbCrLf & outPath)

End Sub

'================ HELPERS ===================

Function GetOccurrenceIndex(list As List(Of ComponentOccurrence), name As String) As Integer
    For i = 0 To list.Count - 1
        If list(i).Name = name Then Return i
    Next
    Return -1
End Function

Function FormatNumber(v As Double) As String
    Return v.ToString("0.################", System.Globalization.CultureInfo.InvariantCulture)
End Function

Function GetProp(doc As Document, setName As String, propName As String) As String
    Try
        Return doc.PropertySets.Item(setName).Item(propName).Value.ToString()
    Catch
        Return ""
    End Try
End Function

Function EscapeJson(s As String) As String
    If String.IsNullOrEmpty(s) Then Return ""
    s = s.Replace("\", "\\").Replace("""", "\""").Replace(vbCr, "").Replace(vbLf, "\n").Replace(vbTab, "\t")
    Return s
End Function
