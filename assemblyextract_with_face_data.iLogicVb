Sub Main()

    Dim asmDoc As Inventor.AssemblyDocument =
        TryCast(ThisApplication.ActiveDocument, Inventor.AssemblyDocument)

    If asmDoc Is Nothing Then
        MessageBox.Show("This rule must run inside an Assembly (.iam)")
        Exit Sub
    End If

    Dim asmDef As Inventor.AssemblyComponentDefinition = asmDoc.ComponentDefinition
    Dim sb As New System.Text.StringBuilder()
    Dim Q As String = Chr(34)

    sb.AppendLine("{")

    '================ ASSEMBLY METADATA =================
    sb.AppendLine("  " & Q & "assembly_metadata" & Q & ": {")
    sb.AppendLine("    " & Q & "assembly_name" & Q & ": " & Q & EscapeJson(asmDoc.DisplayName) & Q & ",")
    sb.AppendLine("    " & Q & "full_file_path" & Q & ": " & Q &
                  EscapeJson(asmDoc.FullFileName.Replace("\", "/")) & Q & ",")

    Dim massVal As Double = 0
    Try : massVal = asmDef.MassProperties.Mass : Catch : End Try

    sb.AppendLine("    " & Q & "mass_kg" & Q & ": " & FormatNumber(massVal) & ",")
    sb.AppendLine("    " & Q & "extraction_timestamp" & Q & ": " & Q &
                  DateTime.Now.ToString("yyyy-MM-ddTHH:mm:ss") & Q)
    sb.AppendLine("  },")

    '================ COMPONENTS =================
    sb.AppendLine("  " & Q & "components" & Q & ": [")

    Dim occs = asmDef.Occurrences.AllLeafOccurrences
    Dim idx As Integer = 0

    For Each occ As Inventor.ComponentOccurrence In occs

        Dim bbox As Inventor.Box = Nothing
        Try : bbox = occ.RangeBox : Catch : End Try

        Dim sx As Double = 0, sy As Double = 0, sz As Double = 0
        If bbox IsNot Nothing Then
            sx = Math.Abs(bbox.MaxPoint.X - bbox.MinPoint.X)
            sy = Math.Abs(bbox.MaxPoint.Y - bbox.MinPoint.Y)
            sz = Math.Abs(bbox.MaxPoint.Z - bbox.MinPoint.Z)
        End If

        sb.AppendLine("    {")
        sb.AppendLine("      " & Q & "occurrence_name" & Q & ": " & Q &
                      EscapeJson(occ.Name) & Q & ",")
        sb.AppendLine("      " & Q & "dimensions_mm" & Q & ": { " &
                      Q & "x" & Q & ": " & FormatNumber(sx * 10) & ", " &
                      Q & "y" & Q & ": " & FormatNumber(sy * 10) & ", " &
                      Q & "z" & Q & ": " & FormatNumber(sz * 10) & " }")
        sb.Append("    }")

        idx += 1
        If idx < occs.Count Then sb.AppendLine(",") Else sb.AppendLine()
    Next

    sb.AppendLine("  ]")
    sb.AppendLine("}")

    Dim outPath As String =
        System.IO.Path.ChangeExtension(asmDoc.FullFileName, "_export.json")

    System.IO.File.WriteAllText(outPath, sb.ToString())

    MessageBox.Show("✅ Export complete" & vbCrLf & outPath)

End Sub

'================ HELPERS =================

Function FormatNumber(value As Double) As String
    Return value.ToString("0.################",
        System.Globalization.CultureInfo.InvariantCulture)
End Function

Function EscapeJson(str As String) As String
    If String.IsNullOrEmpty(str) Then Return ""
    str = str.Replace("\", "\\")
    str = str.Replace(Chr(34), "\" & Chr(34))
    str = str.Replace(vbCr, "")
    str = str.Replace(vbLf, "\n")
    Return str
End Function
